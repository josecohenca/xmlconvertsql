-- *************************
-- * uniGone modifications :
-- *************************
-- the modifications made by uniGone are prefixed by "uniGone"
--
-- in order to minimize the number of types, IMPORTed modules have been locally
-- defined - in no way ASN.1 definitions have been modified
--
-- Modules are imported from CAP {ccitt(0) identified-organization(4) etsi(0) mobileDomain(0) gsm-Network(1) modules(3)cap-datatypes(52) version2(1)}
--                           definitions (3GPP 09.78 - 710)
-- Modules Object Identifiers have been removed to indicate this is not the 'standard' module.           
--

CAP-DataTypes
DEFINITIONS IMPLICIT TAGS	::=

BEGIN

DestinationRoutingAddress			::= SEQUENCE SIZE (1) OF CalledPartyNumber
--	Indicates the Called Party Number, including service selection information. Refer to GSM 
--	04.08 [25] for encoding. This data type carries only the "type of number", "numbering plan
--	identification" and "number digit" fields defined in [25]; it does not carry the "called
--	party BCD number IEI" or "length of called party BCD number contents".

CalledPartyNumber					::= OCTET STRING (SIZE (minCalledPartyNumberLength .. maxCalledPartyNumberLength))
minCalledPartyNumberLength			INTEGER ::= 3
maxCalledPartyNumberLength			INTEGER ::= 12

END
