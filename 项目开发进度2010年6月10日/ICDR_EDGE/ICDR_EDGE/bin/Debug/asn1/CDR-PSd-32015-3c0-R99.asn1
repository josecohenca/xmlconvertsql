--
-- The ASN.1 syntax has been extracted from 3GPP TS 32.015 V3.12.0 (2003-12)
--
-- *************************
-- * uniGone modifications :
-- *************************
-- the modifications made by uniGone are prefixed by "uniGone"
--
-- in order to minimize the number of types, IMPORTed modules have been locally
-- defined see xxx-imports.asn1 files - in no way ASN.1 definitions have been modified
--

GPRS-Charging-DataTypes  {ccitt (0) identified-organization (4) etsi (0) mobileDomain (0) umts-Operation-Maintenance (3) ts-32-015 (15) informationModel (0) asn1Module (2) version1 (1)}

DEFINITIONS IMPLICIT TAGS	::=

BEGIN

-- EXPORTS everything

IMPORTS	

CellId, Diagnostics, CallDuration, ManagementExtensions, TimeStamp, MSISDN, LocationAreaCode, MessageReference, RecordingEntity, SMSResult, LevelOfCAMELService, CalledNumber, CallingNumber,
CallEventRecordType -- uniGone added 
FROM GSM1205-DataTypes{ ccitt (0) identified-organization (4) etsi(0) mobileDomain (0) gsm-Operation-Maintenance (3) moduleId (3) gsm-12-05 (5) informationModel (0) asn1Module (2) 1 }

/* uniGone module added locally (see MAP-imports.asn1)
AddressString, ISDN-AddressString, IMSI, IMEI
FROM MAP-CommonDataTypes { ccitt identified-organization (4) etsi(0) mobileDomain (0) gsm-Network (1) modules (3) map-CommonDataTypes (18) version6 (6) }
*/
AddressString, ISDN-AddressString, IMSI, IMEI
FROM MAP-CommonDataTypes

/* uniGone module added locally (see MAP-imports.asn1)
CallReferenceNumber
FROM MAP-CH-DataTypes {ccitt(0) identified-organization(4) etsi(0) mobileDomain(0) gsm-network(1) modules(3) map-CH-DataTypes(13) version6(6)}
*/
CallReferenceNumber
FROM MAP-CH-DataTypes 

/* uniGone module added locally (see MAP-imports.asn1)
DefaultGPRS-Handling, DefaultSMS-Handling, ServiceKey
FROM MAP-MS-DataTypes { ccitt identified-organization (4) etsi (0) mobileDomain (0) gsm-Network (1) modules (3) map-MS-DataTypes (11) version6 (6) }
*/
DefaultGPRS-Handling, DefaultSMS-Handling, ServiceKey
FROM MAP-MS-DataTypes

/* uniGone module added locally (see Attribute-ASN1Module-imports.asn1)
ManagementExtension
FROM Attribute-ASN1Module {joint-iso-ccitt ms (9) smi (3) part2 (2) asn1Module (2) 1}
*/
ManagementExtension
FROM Attribute-ASN1Module

-- uniGone added
MOCallRecord, MTCallRecord, RoamingRecord, IncGatewayRecord, OutGatewayRecord, TransitCallRecord,
MOSMSRecord, MTSMSRecord, MOSMSIWRecord, MTSMSGWRecord, SSActionRecord, HLRIntRecord, 
LocUpdateHLRRecord, LocUpdateVLRRecord, CommonEquipRecord, ManagementExtensions, TermCAMELRecord
FROM TS32205-DataTypes {itu-t (0) identified-organization (4) etsi(0) mobileDomain (0) umts-Operation-Maintenance (3) ts-32-205 (205) informationModel (0) asn1Module (2) version1 (1)}
;
--
-- Note that the syntax of AE-title to be used is from 
-- CCITT Rec. X.227 / ISO 8650 corrigendum and not "ANY"
--
------------------------------------------------------------------------------
--
--  CALL AND EVENT RECORDS
--
------------------------------------------------------------------------------

CallEventRecord	::= CHOICE 
{
-- Record values 0..16 are 3G curcuit switch specific
-- 
	moCallRecord		[0] MOCallRecord,
	mtCallRecord		[1] MTCallRecord,
	roamingRecord		[2] RoamingRecord,
	incGatewayRecord	[3] IncGatewayRecord,
	outGatewayRecord	[4] OutGatewayRecord,
	transitRecord		[5] TransitCallRecord,
	moSMSRecord			[6] MOSMSRecord,
	mtSMSRecord			[7] MTSMSRecord,
	moSMSIWRecord		[8] MOSMSIWRecord,
	mtSMSGWRecord		[9] MTSMSGWRecord,
	ssActionRecord		[10] SSActionRecord,
	hlrIntRecord		[11] HLRIntRecord,
	locUpdateHLRRecord	[12] LocUpdateHLRRecord,
	locUpdateVLRRecord	[13] LocUpdateVLRRecord,
	commonEquipRecord	[14] CommonEquipRecord,
	recTypeExtensions	[15] ManagementExtensions,
	termCAMELRecord		[16] TermCAMELRecord,
--
	sgsnPDPRecord		[20] SGSNPDPRecord,
	ggsnPDPRecord		[21] GGSNPDPRecord,
	sgsnMMRecord		[22] SGSNMMRecord,
	sgsnSMORecord		[23] SGSNSMORecord,
	sgsnSMTRecord		[24] SGSNSMTRecord
}

GGSNPDPRecord 	::= SET
{
	recordType				[0] CallEventRecordType,
	networkInitiation		[1] NetworkInitiatedPDPContext OPTIONAL,
	servedIMSI				[3] IMSI,
	ggsnAddress				[4] GSNAddress,
	chargingID				[5] ChargingID,
	sgsnAddress				[6] SEQUENCE OF GSNAddress,
	accessPointNameNI		[7] AccessPointNameNI,
	pdpType					[8] PDPType,
	servedPDPAddress		[9] PDPAddress OPTIONAL,
	dynamicAddressFlag		[11] DynamicAddressFlag OPTIONAL,
	listOfTrafficVolumes	[12] SEQUENCE OF ChangeOfCharCondition,
	recordOpeningTime		[13] TimeStamp,
	duration				[14] CallDuration,
	causeForRecClosing		[15] CauseForRecClosing,
	diagnostics				[16] Diagnostics OPTIONAL,
	recordSequenceNumber	[17] INTEGER OPTIONAL,
	nodeID					[18] NodeID OPTIONAL,
	recordExtensions		[19] ManagementExtensions OPTIONAL,
	localSequenceNumber		[20] LocalSequenceNumber OPTIONAL,
	apnSelectionMode		[21] APNSelectionMode OPTIONAL,
	servedMSISDN			[22] MSISDN OPTIONAL,
	chargingCharacteristics	[23] ChargingCharacteristics OPTIONAL,
	sgsnPLMNIdentifier		[27] PLMN-Id
}

SGSNMMRecord	::= SET
{
	recordType				[0] CallEventRecordType,
	servedIMSI				[1] IMSI,
	servedIMEI				[2] IMEI OPTIONAL,
	sgsnAddress				[3] GSNAddress,
	msNetworkCapability		[4] MSNetworkCapability OPTIONAL,
	routingArea				[5] RoutingAreaCode OPTIONAL,
	locationAreaCode		[6] LocationAreaCode OPTIONAL,
	cellIdentifier			[7] CellId OPTIONAL,
	changeLocation			[8] SEQUENCE OF ChangeLocation OPTIONAL,
	recordOpeningTime		[9] TimeStamp,
	duration				[10] CallDuration OPTIONAL, 
	sgsnChange				[11] SGSNChange OPTIONAL,
	causeForRecClosing		[12] CauseForRecClosing,
	diagnostics				[13] Diagnostics OPTIONAL,
	recordSequenceNumber	[14] INTEGER OPTIONAL,
	nodeID					[15] NodeID OPTIONAL,
	recordExtensions		[16] ManagementExtensions OPTIONAL,
	localSequenceNumber		[17] LocalSequenceNumber OPTIONAL,
	servedMSISDN			[18] MSISDN OPTIONAL,
	chargingCharacteristics	[19] ChargingCharacteristics OPTIONAL,
	cAMELInformationMM 		[20] CAMELInformationMM OPTIONAL,
	systemType				[21] SystemType OPTIONAL

}

SGSNPDPRecord 	::= SET
{
	recordType				[0] CallEventRecordType,
	networkInitiation		[1] NetworkInitiatedPDPContext OPTIONAL,
	servedIMSI				[3] IMSI,
	servedIMEI				[4] IMEI OPTIONAL,
	sgsnAddress				[5] GSNAddress,
	msNetworkCapability		[6] MSNetworkCapability OPTIONAL,
	routingArea				[7] RoutingAreaCode OPTIONAL,
	locationAreaCode		[8] LocationAreaCode OPTIONAL,
	cellIdentifier			[9] CellId OPTIONAL,
	chargingID				[10] ChargingID,
	ggsnAddressUsed			[11] GSNAddress,
	accessPointNameNI		[12] AccessPointNameNI,
	pdpType					[13] PDPType,
	servedPDPAddress		[14] PDPAddress OPTIONAL,
	listOfTrafficVolumes	[15] SEQUENCE OF ChangeOfCharCondition,
	recordOpeningTime		[16] TimeStamp,
	duration				[17] CallDuration,
	sgsnChange				[18] SGSNChange OPTIONAL,
	causeForRecClosing		[19] CauseForRecClosing,
	diagnostics				[20] Diagnostics OPTIONAL,
	recordSequenceNumber	[21] INTEGER OPTIONAL,
	nodeID					[22] NodeID OPTIONAL,
	recordExtensions		[23] ManagementExtensions OPTIONAL,
	localSequenceNumber		[24] LocalSequenceNumber OPTIONAL,
	apnSelectionMode		[25] APNSelectionMode OPTIONAL,
	accessPointNameOI		[26] AccessPointNameOI,
	servedMSISDN			[27] MSISDN OPTIONAL,
	chargingCharacteristics	[28] ChargingCharacteristics OPTIONAL,
	systemType				[29] SystemType OPTIONAL,
	cAMELInformationPDP  	[30] CAMELInformationPDP OPTIONAL,
	rNCUnsentDownlinkVolume	[31] DataVolumeGPRS OPTIONAL
}

SGSNSMORecord	::= SET
{
	recordType				[0] CallEventRecordType,
	servedIMSI				[1] IMSI,
	servedIMEI				[2] IMEI OPTIONAL,
	servedMSISDN			[3] MSISDN OPTIONAL,
	msNetworkCapability		[4] MSNetworkCapability,
	serviceCentre			[5] AddressString,
	recordingEntity			[6] RecordingEntity,
	locationArea			[7] LocationAreaCode OPTIONAL,
	routingArea				[8] RoutingAreaCode OPTIONAL,
	cellIdentifier			[9] CellId OPTIONAL,
	messageReference		[10] MessageReference,
	originationTime			[11] TimeStamp,
	smsResult				[12] SMSResult OPTIONAL,
	recordExtensions		[13] ManagementExtensions OPTIONAL, 
	nodeID					[14] NodeID OPTIONAL,
	localSequenceNumber		[15] LocalSequenceNumber OPTIONAL,
	chargingCharacteristics	[16] ChargingCharacteristics OPTIONAL,
	systemType				[17] SystemType OPTIONAL,
	destinationNumber		[18] CalledNumber OPTIONAL,
	cAMELInformationSMS		[19] CAMELInformationSMS OPTIONAL
}

SGSNSMTRecord	::= SET
{
	recordType				[0] CallEventRecordType,
	servedIMSI				[1] IMSI,
	servedIMEI				[2] IMEI OPTIONAL,
	servedMSISDN			[3] MSISDN OPTIONAL,
	msNetworkCapability		[4] MSNetworkCapability,
	serviceCentre			[5] AddressString,
	recordingEntity			[6] RecordingEntity,
	locationArea			[7] LocationAreaCode OPTIONAL,
	routingArea				[8] RoutingAreaCode OPTIONAL,
	cellIdentifier			[9] CellId OPTIONAL,
	originationTime			[10] TimeStamp,
	smsResult				[11] SMSResult OPTIONAL,
	recordExtensions		[12] ManagementExtensions OPTIONAL,
	nodeID					[13] NodeID OPTIONAL,
	localSequenceNumber		[14] LocalSequenceNumber OPTIONAL,
	chargingCharacteristics	[15] ChargingCharacteristics OPTIONAL,
	systemType				[16] SystemType OPTIONAL

}

------------------------------------------------------------------------------
--
--  OBJECT IDENTIFIERS
--
------------------------------------------------------------------------------

gsm1205InformationModel	 OBJECT IDENTIFIER	::=
	{ ccitt (0) identified-organization (4) etsi (0) mobileDomain (0)
	gsm-Operation-Maintenance (3) gsm-12-05 (5) informationModel (0) }

gsm1205ASN1Module	OBJECT IDENTIFIER	::= 
	{ gsm1205InformationModel asn1Module(2) }

------------------------------------------------------------------------------
--
--  COMMON DATA TYPES
--
------------------------------------------------------------------------------

AccessPointNameNI	::= IA5String (SIZE(1..63))
	--
	-- Network Identifier part of APN in "dot" representation
	-- For example, if the complete APN is 'apn1a.apn1b.apn1c.mnc022.mcc111.gprs'
	-- NI is 'apn1a.apn1b.apn1c' and is presented in this form in the CDR.

AccessPointNameOI	::= IA5String (SIZE(1..37))
	--
	-- Operator Identifier part of APN in "dot" representation
	-- In the 'apn1a.apn1b.apn1c.mnc022.mcc111.gprs' example, the OI portion is 'mnc022.mcc111.gprs'
	-- and is presented in this form in the CDR.

APNSelectionMode::= ENUMERATED
{
	--
	-- See Information Elements TS 29.060
	--
	mSorNetworkProvidedSubscriptionVerified		(0),
	mSProvidedSubscriptionNotVerified			(1),
	networkProvidedSubscriptionNotVerified		(2)
}

CAMELAccessPointNameNI	::= AccessPointNameNI

CAMELAccessPointNameOI	::= AccessPointNameOI

CAMELInformationMM	::= SET 
{
	sCFAddress					[1] SCFAddress OPTIONAL,
	serviceKey					[2]	ServiceKey OPTIONAL,
	defaultTransactionHandling	[3]	DefaultGPRS-Handling OPTIONAL,
	numberOfDPEncountered  		[4] NumberOfDPEncountered OPTIONAL,
	levelOfCAMELService			[5] LevelOfCAMELService OPTIONAL,
	freeFormatData				[6] FreeFormatData OPTIONAL,
	fFDAppendIndicator	     	[7]	FFDAppendIndicator OPTIONAL
}

CAMELInformationPDP	::= SET
{
	sCFAddress					[1] SCFAddress OPTIONAL,
	serviceKey					[2]	ServiceKey OPTIONAL,
	defaultTransactionHandling	[3]	DefaultGPRS-Handling OPTIONAL,
	cAMELAccessPointNameNI		[4] CAMELAccessPointNameNI OPTIONAL,
	cAMELAccessPointNameOI		[5] CAMELAccessPointNameOI OPTIONAL,
	numberOfDPEncountered  		[6] NumberOfDPEncountered OPTIONAL,
	levelOfCAMELService			[7] LevelOfCAMELService OPTIONAL,
	freeFormatData				[8]	FreeFormatData OPTIONAL,
	fFDAppendIndicator	     	[9]	FFDAppendIndicator OPTIONAL
}

CAMELInformationSMS	::= SET 
{
	sCFAddress							[1] SCFAddress OPTIONAL,
	serviceKey							[2]	ServiceKey OPTIONAL,
	defaultSMSHandling					[3]	DefaultSMS-Handling OPTIONAL,
	cAMELCallingPartyNumber				[4] CallingNumber OPTIONAL,
	cAMELDestinationSubscriberNumber	[5] CalledNumber OPTIONAL,
	cAMELSMSCAddress					[6] AddressString OPTIONAL,
	freeFormatData						[7]	FreeFormatData OPTIONAL,
	sMSReferenceNumber					[8] CallReferenceNumber	OPTIONAL
}

CauseForRecClosing	::= INTEGER
{
	--
	-- in GGSN the value sGSNChange should be used for partial record
	-- generation due to SGSN Address List Overflow
	--
	-- cause codes 0 to 15 are defined in TS 32.005 as 'CauseForTerm' (cause for termination)
	--
	normalRelease			(0),
	abnormalRelease			(4),
	cAMELInitCallRelease	(5),
	volumeLimit				(16),
	timeLimit				(17),
	sGSNChange				(18),
	maxChangeCond			(19),
	managementIntervention	(20)
}

ChangeCondition	::= ENUMERATED
{
	qoSChange				(0),
	tariffTime				(1),
	recordClosure			(2)
}

ChangeOfCharCondition	::= SEQUENCE
{
	--
	-- used in PDP context record only
	--
	qosRequested			[1] QoSInformation OPTIONAL,
	qosNegotiated			[2] QoSInformation OPTIONAL,
	dataVolumeGPRSUplink	[3] DataVolumeGPRS,
	dataVolumeGPRSDownlink	[4] DataVolumeGPRS,
	changeCondition			[5] ChangeCondition,
	changeTime				[6] TimeStamp
}

ChangeLocation	::= SEQUENCE
{
	--
	-- used in SGSNMMRecord only
	--
	locationAreaCode	[0] LocationAreaCode,
	routingAreaCode		[1] RoutingAreaCode,
	cellId				[2] CellId OPTIONAL,
	changeTime			[3] TimeStamp
}

ChargingCharacteristics	::= OCTET STRING (SIZE(2))
    --
	--  Descriptions for the bits of the flag set:
	--
	--  Bit 1: H (Hot billing)			:= '00000001'B
	--  Bit 2: F (Flat rate)			:= '00000010'B
	--  Bit 3: P (Prepaid service)		:= '00000100'B
	--	Bit 4: N (Normal billing)		:= '00001000'B
	--	Bit 5: - (Reserved, set to 0)	:= '00010000'B
	--	Bit 6: - (Reserved, set to 0)	:= '00100000'B
	--	Bit 7: - (Reserved, set to 0)	:= '01000000'B
	--	Bit 8: - (Reserved, set to 0)	:= '10000000'B
	--

ChargingID	::= INTEGER (0..4294967295)
	--
	-- generated in GGSN, part of PDP context, see TS 23.060
	-- 0..4294967295 is equivalent to 0..2**32-1

DataVolumeGPRS	::= INTEGER
	--
	-- The volume of data transferred in octets.
	--

DynamicAddressFlag	::= BOOLEAN

ETSIAddress	::= AddressString
	--
	--first octet for nature of address, and numbering plan indicator (3 for X.121)
	--other octets TBCD
	-- See TS 29.002
	--

FFDAppendIndicator	::= BOOLEAN

FreeFormatData	::=	OCTET STRING (SIZE(1..160))
	--
	-- Free formated data as sent in the FurnishChargingInformationGPRS 
	-- see TS 29.078
	--

GSNAddress	::= IPAddress

GSMQoSInformation	::=SEQUENCE
{
	reliability		[0] QoSReliability,
	delay			[1] QoSDelay,
	precedence		[2] QoSPrecedence,
	peakThroughput	[3] QoSPeakThroughput,
	meanThroughput	[4] QoSMeanThroughput
}

IPAddress	::= CHOICE
{
	iPBinaryAddress	 			IPBinaryAddress,
	iPTextRepresentedAddress	IPTextRepresentedAddress
}

IPBinaryAddress	::= CHOICE
{
	iPBinV4Address		[0] OCTET STRING (SIZE(4)),
	iPBinV6Address		[1] OCTET STRING (SIZE(16))
}

IPTextRepresentedAddress	::= CHOICE
{	--
	-- IP address in the familiar "dot" notation
	--
	iPTextV4Address		[2] IA5String (SIZE(7..15)),
	iPTextV6Address		[3] IA5String (SIZE(15..45))
}

LocalSequenceNumber ::= INTEGER (0..4294967295)
	--
	-- Sequence number of the record in this node
	-- 0.. 4294967295 is equivalent to 0..2**32-1, unsigned integer in four octets

MSNetworkCapability	::= OCTET STRING (SIZE(1..8))

NetworkInitiatedPDPContext	::= BOOLEAN
	--
	-- Set to true if PDP context was initiated from network side
	--

NodeID	::= IA5String (SIZE(1..20))

PDPAddress	::= CHOICE
{
	iPAddress		[0] IPAddress,
	eTSIAddress		[1] ETSIAddress
}

PDPType		::= OCTET STRING (SIZE(2))
	--
	--OCTET 1: PDP Type Organization
	--OCTET 2: PDP Type Number
	-- See TS 29.060
	--

PLMN-Id		::= OCTET STRING (SIZE (3))
	--	This is a 1:1 copy from the Routing Area Identity (RAI) IE specified in TS 29.060
	--  as follows:
	--	OCTET 1 of PLMN-Id = OCTET 2 of RAI  
	--	OCTET 2 of PLMN-Id = OCTET 3 of RAI  
	--	OCTET 3 of PLMN-Id = OCTET 4 of RAI  


QoSDelay		::= ENUMERATED
{
	--
	-- See Quality of service TS 24.008
	--
	delayClass1		(1),
	delayClass2		(2),
	delayClass3		(3),
	delayClass4		(4)
}

QoSInformation	::= CHOICE
{
	gsmQosInformation		[0] GSMQoSInformation,
	umtsQosInformation		[1] OCTET STRING (SIZE (4..12))
}
-- When dealing with a pre R99 QoS profile the GSN may either choose the "GSMQoSInformation" or the
-- "umtsQoSInformation" encoding. Dealing with R99 QoS profiles the GSN shall apply the
-- "umtsQoSInformation" encoding. The umtsQosInformation octet string is a 1:1 copy of the contents
-- (starting with octet 4) of the "Quality of service Profile" information element specified in
-- 3GPP TS 29.060 [22] for R99 and GSM TS 09.60 for pre R99 cases.

QoSMeanThroughput	::= ENUMERATED
{
	--
	-- See Quality of service TS 24.008
	--
	subscribedMeanThroughput				(0), -- MS to network direction
	-- Network to MS direction needs not to be covered since value (0) = "reserved"
	mean100octetPh			(1),
	mean200octetPh			(2),
	mean500octetPh			(3),
	mean1000octetPh			(4),
	mean2000octetPh			(5),
	mean5000octetPh			(6),
	mean10000octetPh		(7),
	mean20000octetPh		(8),
	mean50000octetPh		(9),
	mean100000octetPh		(10),
	mean200000octetPh		(11),
	mean500000octetPh		(12),
	mean1000000octetPh		(13),
	mean2000000octetPh		(14),
	mean5000000octetPh		(15),
	mean10000000octetPh		(16),
	mean20000000octetPh		(17),
	mean50000000octetPh		(18),
	reserved				(30),
	bestEffort				(31)
}

QoSPeakThroughput	::= ENUMERATED
{
	--
	-- See Quality of service TS 24.008
	--
	unspecified				(0),
	upTo1000octetPs			(1),
	upTo2000octetPs			(2),
	upTo4000octetPs			(3),
	upTo8000octetPs			(4),
	upTo16000octetPs		(5),
	upTo32000octetPs		(6),
	upTo64000octetPs		(7),
	upTo128000octetPs		(8),
	upTo256000octetPs		(9)
}

QoSPrecedence	::= ENUMERATED
{
	--
	-- See Quality of service TS 24.008
	--
	unspecified				(0),
	highPriority			(1),
	normalPriority			(2),
	lowPriority				(3)
}

QoSReliability	::= ENUMERATED
{
	--
	-- See Quality of service TS 24.008
	--
	unspecifiedReliability	(0),
	acknowledgedGTP			(1),
	unackGTPAcknowLLC			(2),
	unackGTPLLCAcknowRLC		(3),
	unackGTPLLCRLC				(4),
	unacknowUnprotectedData	(5)
}

RoutingAreaCode	::= OCTET STRING (SIZE(1))
	--
	-- See TS 24.008
	--

SCFAddress	::= AddressString
	--
	-- See TS 29.002
	--

NumberOfDPEncountered  ::= INTEGER

SGSNChange	::= BOOLEAN
	--
	-- present if first record after inter SGSN routing area update
	-- in new SGSN
	--

SystemType  ::= ENUMERATED
{
	unknown				(0),
	iuUTRAN				(1),
	gERAN				(2)
}

END
