-- Module MTSUpperBounds (X.411:06/1999)

MTSUpperBounds {joint-iso-itu-t mhs(6) mts(3) modules(0) upper-bounds(3)
  version-1999(1)} DEFINITIONS IMPLICIT TAGS ::=
BEGIN

--	Prologue
--	Exports everything
IMPORTS -- nothing -- ;

--	Upper Bounds
ub-additional-info INTEGER ::= 1024

ub-bilateral-info INTEGER ::= 1024

ub-bit-options INTEGER ::= 16

ub-built-in-content-type INTEGER ::= 32767

ub-built-in-encoded-information-types INTEGER ::= 32

ub-certificates INTEGER ::= 64

ub-common-name-length INTEGER ::= 64

ub-content-correlator-length INTEGER ::= 512

ub-content-id-length INTEGER ::= 16

ub-content-length INTEGER ::= 2147483647 -- the largest integer in 32 bits

ub-content-types INTEGER ::= 1024

ub-country-name-alpha-length INTEGER ::= 2

ub-country-name-numeric-length INTEGER ::= 3

ub-diagnostic-codes INTEGER ::= 32767

ub-deliverable-class INTEGER ::= 256

ub-dl-expansions INTEGER ::= 512

ub-domain-defined-attributes INTEGER ::= 4

ub-domain-defined-attribute-type-length INTEGER ::= 8

ub-domain-defined-attribute-value-length INTEGER ::= 128

ub-domain-name-length INTEGER ::= 16

ub-encoded-information-types INTEGER ::= 1024

ub-extension-attributes INTEGER ::= 256

ub-extension-types INTEGER ::= 256

ub-e163-4-number-length INTEGER ::= 15

ub-e163-4-sub-address-length INTEGER ::= 40

ub-generation-qualifier-length INTEGER ::= 3

ub-given-name-length INTEGER ::= 16

ub-initials-length INTEGER ::= 5

ub-integer-options INTEGER ::= 256

ub-labels-and-redirections INTEGER ::= 256

ub-local-id-length INTEGER ::= 32

ub-mta-name-length INTEGER ::= 32

ub-mts-user-types INTEGER ::= 256

ub-numeric-user-id-length INTEGER ::= 32

ub-organization-name-length INTEGER ::= 64

ub-organizational-unit-name-length INTEGER ::= 32

ub-organizational-units INTEGER ::= 4

ub-orig-and-dl-expansions INTEGER ::= 513 -- ub-dl-expansions plus one

ub-password-length INTEGER ::= 62

ub-pds-name-length INTEGER ::= 16

ub-pds-parameter-length INTEGER ::= 30

ub-pds-physical-address-lines INTEGER ::= 6

ub-postal-code-length INTEGER ::= 16

ub-privacy-mark-length INTEGER ::= 128

ub-queue-size INTEGER ::= 2147483647 -- the largest integer in 32 bits

ub-reason-codes INTEGER ::= 32767

ub-recipient-number-for-advice-length INTEGER ::= 32

ub-recipients INTEGER ::= 32767

ub-redirection-classes INTEGER ::= 256

ub-redirections INTEGER ::= 512

ub-restrictions INTEGER ::= 1024

ub-security-categories INTEGER ::= 64

ub-security-labels INTEGER ::= 256

ub-security-problems INTEGER ::= 256

ub-supplementary-info-length INTEGER ::= 256

ub-surname-length INTEGER ::= 40

ub-teletex-private-use-length INTEGER ::= 128

ub-terminal-id-length INTEGER ::= 24

ub-transfers INTEGER ::= 512

ub-tsap-id-length INTEGER ::= 16

ub-unformatted-address-length INTEGER ::= 180

ub-universal-generation-qualifier-length INTEGER ::= 16

ub-universal-given-name-length INTEGER ::= 40

ub-universal-initials-length INTEGER ::= 16

ub-universal-surname-length INTEGER ::= 64

ub-x121-address-length INTEGER ::= 16

END -- of MTSUpperBounds

-- Generated by Asnp, the ASN.1 pretty-printer of France Telecom R&D
